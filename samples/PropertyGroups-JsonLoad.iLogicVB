AddReference "iPropertyGroups.dll"
Imports iPropertyGroups

'Create a PropertyGroups object and load a json file into the object.
Dim oGroups As PropertyGroups = PropertyGroups.LoadJson("C:\Path\to\your\propertygroups-definition.json")

'Get active document object...
Dim oDoc As Inventor.Document = ThisApplication.ActiveDocument

'Apply PropertyGroups object to the document...
oGroups.Item("Stock Part").ApplyToAndOverwrite(oDoc)
